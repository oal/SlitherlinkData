-- INPUT FORMAT
Cell ::= CHOICE {
  value INTEGER (0..4), -- 4 would only ever occur on 1x1 boards, but it would be valid
  empty NULL -- cell without a number (any number of sides)
}


InputBoard ::= SEQUENCE {
  size INTEGER, -- assuming same width and height, as this is the case in the examples
  cells SEQUENCE OF Cell -- use sequence to retain order
}

InputBoardFile ::= SEQUENCE OF InputBoard -- number of boards is implicitly known based on length of sequence

-- SAMPLES IN INPUT FORMAT
sampleBoardFile InputBoardFile ::= {
  {
    size 5,
    cells {
      -- could have left out "value" and "empty" here, but it leads to warnings
      -- in the compiler, so we added them in to be safe.
      empty NULL, empty NULL, empty NULL, value 1,    value 2,
      value 2,    empty NULL, value 3,    empty NULL, empty NULL,
      value 3,    value 3,    empty NULL, value 2,    empty NULL,
      empty NULL, empty NULL, empty NULL, empty NULL, value 1,
      empty NULL, value 3,    empty NULL, empty NULL, empty NULL
    }
  },
  {
    size 7,
    cells {
      -- keeping the value / empty here as well.
      value 3,    empty NULL, empty NULL, value 2,    empty NULL, empty NULL, empty NULL,
      value 1,    empty NULL, empty NULL, empty NULL, empty NULL, value 1,    value 2,
      value 2,    empty NULL, empty NULL, value 2,    value 2,    empty NULL, value 2,
      empty NULL, empty NULL, value 2,    empty NULL, value 1,    empty NULL, value 2,
      empty NULL, value 2,    empty NULL, value 3,    empty NULL, empty NULL, value 2,
      value 3,    empty NULL, empty NULL, value 3,    empty NULL, value 2,    empty NULL,
      empty NULL, value 2,    value 1,    empty NULL, value 3,    value 3,    empty NULL
    }
  }
}
