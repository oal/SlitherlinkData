-- INPUT FORMAT
InputBoard ::= SEQUENCE {
  size INTEGER, -- assuming same width and height, as this is the case in the examples
  cells BIT STRING -- Four bits per cell/number. 0, 1, 2, 3 4 for the numbers and E for empty.
}

InputBoardFile ::= SEQUENCE OF InputBoard -- number of boards is implicitly known based on length of sequence

-- SAMPLES IN INPUT FORMAT
sampleBoardFile InputBoardFile ::= {
  {
    size 5,
    cells '
      EEE12
      2E3EE
      33E2E
      EEEE1
      E3EEE
    'H
  },
  {
    size 7,
    cells '
    3EE2EEE
    1EEEE12
    2EE22E2
    EE2E1E2
    E2E3EE2
    3EE3E2E
    E21E33E
    'H
  }
}
